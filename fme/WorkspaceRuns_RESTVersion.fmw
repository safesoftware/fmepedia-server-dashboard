FME workspace WorkspaceRuns_RESTVersion.fmw
Title: none2none

Parameters:
- Max_Job_Age = 1 month ago   # Only include jobs from
- SERVER_HOST =   # FME Server URL
- SERVER_TOKEN =   # FME Server Token

Writers:
- CSV_1: CSV to $(FME_SHAREDRESOURCE_DATA)ServerDashboard

Creator
    NUM = 1
    GEOMTYPE = Geometry Object
    CREATED -> JobHistoryReader_2
JobHistoryReader_2
    SERVER_HOST = $(SERVER_HOST)
    MAX_JOB_AGE = $(Max_Job_Age)
    SERVER_TOKEN = $(SERVER_TOKEN)
    Server_Version = v2
    -> StringReplacer
    <Rejected> -> JobHistoryReader__Rejected_
AttributeKeeper
    KEEP_ATTRS = Repository,WorkspaceName,JobStatus
    -> Aggregator
Aggregator
    ORDERED = No
    COUNT_ATTR = Runs
    MODE = Geometry - Assemble One Level
    SEP = ,
    AGGREGATE_TYPE = Homogeneous Collection (If Possible)
    ACCUM_ATTRS_NAME = No
    GROUP_BY = JobStatus Repository WorkspaceName
    AGGREGATE -> Aggregator_2
Aggregator_2
    ORDERED = No
    LIST_NAME = _list
    MODE = Attributes Only
    SEP = ,
    ACCUM_ATTRS_NAME = Yes
    GROUP_BY = Repository WorkspaceName
    AGGREGATE -> ListRenamer
ListRenamer
    LIST_NAME = _list{}.JobStatus
    LIST_COMPONENT_NAMES = _list{},_list{},JobStatus{},JobStatus{}
    LIST_ACTION = Promote
    LEAVE_ORIG = No
    -> ListRenamer_2
ListRenamer_2
    LIST_NAME = _list{}.Runs
    LIST_COMPONENT_NAMES = _list{},_list{},Runs{},Runs{}
    LIST_ACTION = Promote
    LEAVE_ORIG = No
    -> RecordBuilder
RecordBuilder
    LIST_ATTR = JobStatus{}
    SRC_LIST = Runs{}
    -> AttributeExposer
AttributeExposer
    ATTR_LIST = SUCCESS,FME_FAILURE,ABORTED
    -> AttributeCreator_2
AttributeCreator_2
    ATTR_LIST = WorkspaceName,<b>@Value(Repository)</b><br/>@Value(WorkspaceName),forSorting,@LowerCase(@Value(WorkspaceName))
    -> Sorter
Sorter
    SORT_PARM = forSorting ALPHA ASCENDING
    SORTED -> AttributeRenamer
AttributeRenamer
    ATTR_LIST = ABORTED,Cancelled,,SUCCESS,Successful,,FME_FAILURE,Failure,
    -> workspaceRuns (writer CSV_1)
workspaceRuns (writer CSV_1)
    attributes: WorkspaceName char(100), Successful auto, Failure auto, Cancelled auto
JobHistoryReader__Rejected_: Logger
    MESSAGE = Feature is:
    MAXFEATS = 20
    MAXCOORDS = 20

Bookmark: Get workspace and repository name
StringReplacer
    CASE = no
    SRC_ATTRS = workspacePath
    FIND_TEXT = "
    NO_MATCH = _FME_NO_OP_
    REGEXP = no
    -> FilenamePartExtractor
FilenamePartExtractor
    DIRPATH_ATTR = folderpath
    FULLNAME_ATTR = WorkspaceName
    SRC_ATTR = @Value(workspacePath)
    -> AttributeSplitter_2
AttributeSplitter_2
    LIST_NAME = _path
    ATTR_NAME = folderpath
    DROP_EMPTY_PARTS = No
    DELIMITER = /
    TRIM_OPTION = Both
    -> AttributeCreator_3
AttributeCreator_3
    ATTR_LIST = Repository,@Value(_path{0}),JobStatus,@Value(status)
    -> AttributeKeeper

FME custom transformer RecordBuilderLoop
Indexes lists from RecordBuilder and creates new attributes from field name and value pairs. Input is a field{} list and a value{} list. Output are new fields as follows:
=
=
etc

Parameters:
- LIST_ATTR = _fields{}   # " " List Fields
- INDEX = @Value(currentIndex)   # List Index
- SRC_LIST = values{}   # " " Source List Values
- currentIndex = @Value(currentIndex)

INPUT (input)
    -> ListCopier_3
ListCopier_3
    DEST_LIST = _fields
    SRC_LIST = $(LIST_ATTR)
    -> ListCopier_2
ListCopier_2
    DEST_LIST = _values
    SRC_LIST = $(SRC_LIST)
    -> AttributeExposer_3
AttributeExposer_3
    ATTR_LIST = _fields{},_fields,_element_count,_values{},_values
    -> ListIndexer_27
ListIndexer_27
    LIST_ATTR = _fields{}
    INDEX = $(INDEX)
    -> ListIndexer_2
ListIndexer_2
    LIST_ATTR = _values{}
    INDEX = $(INDEX)
    -> TCL_AttributeAdd
TCL_AttributeAdd: TCLCaller
    VAL_ATTR = _result
    TCLPROG = attrAdd &_fields &_values
    SRC = proc attrAdd {attr value} {  FME_SetAttribute $attr $value   }
    -> ExpressionEvaluator
ExpressionEvaluator
    VAL_ATTR = currentIndex
    EXPRESSION = $(currentIndex)+1
    -> Tester_5
Tester_5
    TEST_CLAUSE = TEST @Value(currentIndex) < @Value(_element_count)
    TEST_LIST = &currentIndex,<,&_element_count
    BOOL_OP = OR
    TEST_MODE = Automatic
    FAILED -> OUTPUT (output)
    PASSED -> INPUT (output)
INPUT (output)
OUTPUT (output)

FME custom transformer RecordBuilder
Creates new attributes from field name and value pairs. Input is a field{} list and a value{} list. Output are new fields as follows:
=
=
etc
Depends on RecordBuilderLoop to iterate through the field{} and value{} lists.

Parameters:
- LIST_ATTR = _fields{}   # " " Field Names List
- SRC_LIST = _values{}   # " " Field Values List
- REMOVE_ATTRS = _creation_instance,_element_count,_fields,_result,_values,currentIndex,field0,field1,field2,value0,value1,value2   # " " Attributes to Remove

INPUT (input)
    -> ListCopier_3
ListCopier_3
    DEST_LIST = _fields
    SRC_LIST = $(LIST_ATTR)
    -> ListCopier_2
ListCopier_2
    DEST_LIST = _values
    SRC_LIST = $(SRC_LIST)
    -> AttributeExposer_3
Note: RecordBuilder / Creates new attributes from field name and value pairs. / Input is a field{} list and a value{} list. / Output are new fields as follows: / <field1>=<value1> / <field2>=<value2> / etc / Depends on RecordBuilderLoop to iterate through the field{} and value{} lists.
AttributeExposer_3
    ATTR_LIST = _fields{},_fields,_values{},_values
    -> ListElementCounter
ListElementCounter
    LIST_NAME = _fields{}
    CNT_ATTR = _element_count
    -> AttributeCreator_3
AttributeCreator_3
    ATTR_LIST = currentIndex,0
    -> RecordBuilderLoop
RecordBuilderLoop
    LIST_ATTR = _fields{}
    INDEX = @Value(currentIndex)
    SRC_LIST = _values{}
    currentIndex = @Value(currentIndex)
    -> AttributeRemover
AttributeRemover
    REMOVE_ATTRS = $(REMOVE_ATTRS)
    -> ListRemover
ListRemover
    LIST_ATTRS = _fields{} _values{}
    -> OUTPUT (output)
OUTPUT (output)
