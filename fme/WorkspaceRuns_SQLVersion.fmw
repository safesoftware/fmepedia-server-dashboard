FME workspace WorkspaceRuns_SQLVersion.fmw
Title: none2none

Parameters:
- TimePeriod = 1 month ago   # " " Attribute Value

Readers:
- CSV_1: CSV from $(FME_MF_DIR)tempdata/fme_job_history.csv

Writers:
- CSV_2: CSV to $(FME_SHAREDRESOURCE_DATA)ServerDashboard

Creator
    GEOMTYPE = Geometry Object
    NUM = 1
    CREATED -> AttributeCreator_7
SQLExecutor
    FORMAT = POSTGRES
    SQL_STATEMENT:
      SELECT *
      FROM public.fme_job_history
      WHERE "date_started" >= '@Value(lastMonth)'
    COMBINE_GEOM = Initiator Geometry Only
    POSTGRES_PORT = 7080
    EXPOSED_ATTRIBUTE_LIST = request,date_started,engine_instance,date_finished,date_queued,job_status
    COMBINE_ATTRS = Result Attributes Only
    DATASET = fmeserver
    POSTGRES_HOST = localhost
    POSTGRES_USER_NAME = fmeserver
    POSTGRES_QUERY_FEATURE_TYPES_FOR_MERGE_FILTERS = Yes
    POSTGRES_PASSWORD =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
    RESULT -> AttributeSplitter
Note: Convert status codes / to text values.
AttributeValueMapper
    SRC = job_status
    DEFAULT_VALUE = Other
    VAL_ATTR = JobStatus
    LUT = 8,Successful,9,Failure,7,Cancelled
    DIRECTION = Forward (Source To Destination)
    -> AttributeKeeper
AttributeKeeper
    KEEP_ATTRS = Repository,WorkspaceName,JobStatus
    -> Aggregator
Aggregator
    COUNT_ATTR = Runs
    GROUP_BY = JobStatus Repository WorkspaceName
    ORDERED = No
    AGGREGATE_TYPE = Homogeneous Collection (If Possible)
    SEP = ,
    MODE = Geometry - Assemble One Level
    ACCUM_ATTRS_NAME = No
    AGGREGATE -> Aggregator_2
Aggregator_2
    GROUP_BY = Repository WorkspaceName
    ORDERED = No
    SEP = ,
    MODE = Attributes Only
    LIST_NAME = _list
    ACCUM_ATTRS_NAME = Yes
    AGGREGATE -> ListRenamer
ListRenamer
    LIST_NAME = _list{}.JobStatus
    LIST_COMPONENT_NAMES = _list{},_list{},JobStatus{},JobStatus{}
    LEAVE_ORIG = No
    LIST_ACTION = Promote
    -> ListRenamer_2
ListRenamer_2
    LIST_NAME = _list{}.Runs
    LIST_COMPONENT_NAMES = _list{},_list{},Runs{},Runs{}
    LEAVE_ORIG = No
    LIST_ACTION = Promote
    -> RecordBuilder
RecordBuilder
    SRC_LIST = Runs{}
    LIST_ATTR = JobStatus{}
    -> AttributeExposer
AttributeExposer
    ATTR_LIST = Successful,Failure,Cancelled
    -> AttributeCreator_2
AttributeCreator_2
    ATTR_LIST = WorkspaceName,<b>@Value(Repository)</b><br/>@Value(WorkspaceName),forSorting,@LowerCase(@Value(WorkspaceName))
    -> Sorter
Sorter
    SORT_PARM = forSorting ALPHA ASCENDING
    SORTED -> workspaceRuns (writer CSV_2)
workspaceRuns (writer CSV_2)
    attributes: WorkspaceName char(100), Successful auto, Failure auto, Cancelled auto

Bookmark: Get date one month ago
AttributeCreator_7
    ATTR_LIST = lastMonth,$(TimePeriod)
    -> DateFormatter_5
DateFormatter_5
    FMT = ISO DateTime (%Y-%m-%dT%H:%M:%S)
    INVALID_DATE_VALUE = _FME_NO_OP_
    SRCFMT = Unknown - Automatic Detection
    DATE_ATTR = lastMonth
    -> SQLExecutor

Bookmark: Get workspace and repository name
AttributeSplitter
    LIST_NAME = _list
    TRIM_OPTION = Both
    ATTR_NAME = request
    DELIMITER = "
    DROP_EMPTY_PARTS = No
    -> FilenamePartExtractor
FilenamePartExtractor
    SRC_ATTR = @Value(_list{1})
    DIRPATH_ATTR = folderpath
    FULLNAME_ATTR = WorkspaceName
    -> AttributeSplitter_2
AttributeSplitter_2
    LIST_NAME = _path
    TRIM_OPTION = Both
    ATTR_NAME = folderpath
    DELIMITER = /
    DROP_EMPTY_PARTS = No
    -> AttributeCreator_3
AttributeCreator_3
    ATTR_LIST = Repository,@Value(_path{0})
    -> AttributeValueMapper

Bookmark: Local Testing
CSV (reader CSV_1)
    attributes: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

FME custom transformer RecordBuilderLoop
Indexes lists from RecordBuilder and creates new attributes from field name and value pairs. Input is a field{} list and a value{} list. Output are new fields as follows:
=
=
etc

Parameters:
- LIST_ATTR = _fields{}   # " " List Fields
- INDEX = @Value(currentIndex)   # List Index
- SRC_LIST = values{}   # " " Source List Values
- currentIndex = @Value(currentIndex)

INPUT (input)
    -> ListCopier_3
ListCopier_3
    SRC_LIST = $(LIST_ATTR)
    DEST_LIST = _fields
    -> ListCopier_2
ListCopier_2
    SRC_LIST = $(SRC_LIST)
    DEST_LIST = _values
    -> AttributeExposer_3
AttributeExposer_3
    ATTR_LIST = _fields{},_fields,_element_count,_values{},_values
    -> ListIndexer_27
ListIndexer_27
    LIST_ATTR = _fields{}
    INDEX = $(INDEX)
    -> ListIndexer_2
ListIndexer_2
    LIST_ATTR = _values{}
    INDEX = $(INDEX)
    -> TCL_AttributeAdd
TCL_AttributeAdd: TCLCaller
    SRC = proc attrAdd {attr value} {  FME_SetAttribute $attr $value   }
    VAL_ATTR = _result
    TCLPROG = attrAdd &_fields &_values
    -> ExpressionEvaluator
ExpressionEvaluator
    EXPRESSION = $(currentIndex)+1
    VAL_ATTR = currentIndex
    -> Tester_5
Tester_5
    TEST_LIST = &currentIndex,<,&_element_count
    TEST_CLAUSE = TEST @Value(currentIndex) < @Value(_element_count)
    BOOL_OP = OR
    TEST_MODE = Automatic
    FAILED -> OUTPUT (output)
    PASSED -> INPUT (output)
INPUT (output)
OUTPUT (output)

FME custom transformer RecordBuilder
Creates new attributes from field name and value pairs. Input is a field{} list and a value{} list. Output are new fields as follows:
=
=
etc
Depends on RecordBuilderLoop to iterate through the field{} and value{} lists.

Parameters:
- LIST_ATTR = _fields{}   # " " Field Names List
- SRC_LIST = _values{}   # " " Field Values List
- REMOVE_ATTRS = _creation_instance,_element_count,_fields,_result,_values,currentIndex,field0,field1,field2,value0,value1,value2   # " " Attributes to Remove

INPUT (input)
    -> ListCopier_3
ListCopier_3
    SRC_LIST = $(LIST_ATTR)
    DEST_LIST = _fields
    -> ListCopier_2
ListCopier_2
    SRC_LIST = $(SRC_LIST)
    DEST_LIST = _values
    -> AttributeExposer_3
Note: RecordBuilder / Creates new attributes from field name and value pairs. / Input is a field{} list and a value{} list. / Output are new fields as follows: / <field1>=<value1> / <field2>=<value2> / etc / Depends on RecordBuilderLoop to iterate through the field{} and value{} lists.
AttributeExposer_3
    ATTR_LIST = _fields{},_fields,_values{},_values
    -> ListElementCounter
ListElementCounter
    LIST_NAME = _fields{}
    CNT_ATTR = _element_count
    -> AttributeCreator_3
AttributeCreator_3
    ATTR_LIST = currentIndex,0
    -> RecordBuilderLoop
RecordBuilderLoop
    SRC_LIST = _values{}
    LIST_ATTR = _fields{}
    INDEX = @Value(currentIndex)
    currentIndex = @Value(currentIndex)
    -> AttributeRemover
AttributeRemover
    REMOVE_ATTRS = $(REMOVE_ATTRS)
    -> ListRemover
ListRemover
    LIST_ATTRS = _fields{} _values{}
    -> OUTPUT (output)
OUTPUT (output)
