FME workspace RuntimePerEngine_RESTVersion.fmw
Title: none2none

Parameters:
- TimePeriod = 1 month ago   # " " Attribute Value

Writers:
- CSV_1: CSV to $(FME_SHAREDRESOURCE_DATA)ServerDashboard

Creator
    GEOMTYPE = Geometry Object
    NUM = 1
    CREATED -> JobHistoryReader
JobHistoryReader
    SERVER_TOKEN =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
    SERVER_HOST = https://bluesky-safe-software.fmecloud.com
    MAX_JOB_AGE = $(TimePeriod)
    -> AttributeCopier
    <Rejected> -> Terminator
Note: Calculate total runtime / per engine
Aggregator
    GROUP_BY = Date engineName
    SEP = ,
    ACCUM_ATTRS_NAME = Yes
    MODE = Attributes Only
    ORDERED = No
    SUM = RunTime
    AGGREGATE -> AttributeCreator_3
AttributeCreator_3
    ATTR_LIST = SortDate,@Value(Date)
    -> DateFormatter_6
DateFormatter_6
    DATE_ATTR = Date
    FMT = %b %e %Y
    SRCFMT = Unknown - Automatic Detection
    INVALID_DATE_VALUE = _FME_NO_OP_
    -> Aggregator_2
Note: Sort by date
Sorter
    SORT_PARM = _list{0}.SortDate ALPHA ASCENDING
    SORTED -> runtimePerEngine (writer CSV_1)
runtimePerEngine (writer CSV_1)
    attributes: Date auto, localhost_Engine1 auto, localhost_Engine2 auto, localhost_Engine3 auto, localhost_Engine4 auto, TotalRunTime auto
Terminator
    MESSAGE = Translation Terminated: There was an error accessing job history.

Bookmark: Calculate Run Time
AttributeCopier
    ATTR_LIST = timeFinished,date_finished_epoch,,timeStarted,date_started_epoch,
    -> DateFormatter_3
DateFormatter_3
    DATE_ATTR = date_finished_epoch,date_started_epoch
    FMT = %s
    SRCFMT = %Y-%m-%dT%H:%M:%SZ
    INVALID_DATE_VALUE = _FME_NO_OP_
    -> AttributeCreator_2
AttributeCreator_2
    ATTR_LIST = RunTime,@Evaluate(@Value(date_finished_epoch)-@Value(date_started_epoch))
    -> DateFormatter

Bookmark: Attribute Cleanup
DateFormatter
    DATE_ATTR = timeFinished
    FMT = FME Date (%Y%m%d)
    SRCFMT = %Y-%m-%dT%H:%M:%SZ
    INVALID_DATE_VALUE = _FME_NO_OP_
    -> AttributeKeeper_2
AttributeKeeper_2
    KEEP_ATTRS = RunTime,engineName,timeFinished
    -> AttributeCreator_5
AttributeCreator_5
    ATTR_LIST = Date,@Value(timeFinished)
    -> Aggregator

Bookmark: Group by Date
Aggregator_2
    GROUP_BY = Date
    SEP = ,
    LIST_NAME = _list
    ACCUM_ATTRS_NAME = Yes
    MODE = Attributes Only
    ORDERED = No
    AGGREGATE -> ListRenamer
ListRenamer
    LIST_ACTION = Promote
    LIST_COMPONENT_NAMES = _list{},_list{},engineName{},engineName{}
    LIST_NAME = _list{}.engineName
    LEAVE_ORIG = No
    -> ListRenamer_2
ListRenamer_2
    LIST_ACTION = Promote
    LIST_COMPONENT_NAMES = _list{},_list{},RunTime{},RunTime{}
    LIST_NAME = _list{}.RunTime
    LEAVE_ORIG = No
    -> RecordBuilder
RecordBuilder
    SRC_LIST = RunTime{}
    LIST_ATTR = engineName{}
    -> AttributeExposer_2

Bookmark: Create attributes for output
AttributeExposer_2
    ATTR_LIST = localhost_Engine1,localhost_Engine2,localhost_Engine3,localhost_Engine4
    -> NullAttributeMapper
NullAttributeMapper
    ATTRCHOICE = Selected Attributes
    SOURCE_ATTR_VAL = "Missing (Selected Attributes Only)"
    ATTRLIST = localhost_Engine1 localhost_Engine2 localhost_Engine3 localhost_Engine4
    NEW_VALUE = 0
    NULL_TREATMENT = New Value
    -> ListSummer
ListSummer
    SRC_LIST = RunTime{}
    RESULT = TotalRunTime
    -> Sorter

FME custom transformer RecordBuilder
Creates new attributes from field name and value pairs. Input is a field{} list and a value{} list. Output are new fields as follows:
=
=
etc
Depends on RecordBuilderLoop to iterate through the field{} and value{} lists.

Parameters:
- LIST_ATTR = _fields{}   # " " Field Names List
- SRC_LIST = _values{}   # " " Field Values List
- REMOVE_ATTRS = _creation_instance,_element_count,_fields,_result,_values,currentIndex,field0,field1,field2,value0,value1,value2   # " " Attributes to Remove

INPUT (input)
    -> ListCopier_3
ListCopier_3
    SRC_LIST = $(LIST_ATTR)
    DEST_LIST = _fields
    -> ListCopier_2
ListCopier_2
    SRC_LIST = $(SRC_LIST)
    DEST_LIST = _values
    -> AttributeExposer_3
Note: RecordBuilder / Creates new attributes from field name and value pairs. / Input is a field{} list and a value{} list. / Output are new fields as follows: / <field1>=<value1> / <field2>=<value2> / etc / Depends on RecordBuilderLoop to iterate through the field{} and value{} lists.
AttributeExposer_3
    ATTR_LIST = _fields{},_fields,_values{},_values
    -> ListElementCounter
ListElementCounter
    LIST_NAME = _fields{}
    CNT_ATTR = _element_count
    -> AttributeCreator_3
AttributeCreator_3
    ATTR_LIST = currentIndex,0
    -> RecordBuilderLoop
RecordBuilderLoop
    currentIndex = @Value(currentIndex)
    SRC_LIST = _values{}
    INDEX = @Value(currentIndex)
    LIST_ATTR = _fields{}
    -> AttributeRemover
AttributeRemover
    REMOVE_ATTRS = $(REMOVE_ATTRS)
    -> ListRemover
ListRemover
    LIST_ATTRS = _fields{} _values{}
    -> OUTPUT (output)
OUTPUT (output)

FME custom transformer RecordBuilderLoop
Indexes lists from RecordBuilder and creates new attributes from field name and value pairs. Input is a field{} list and a value{} list. Output are new fields as follows:
=
=
etc

Parameters:
- LIST_ATTR = _fields{}   # " " List Fields
- INDEX = @Value(currentIndex)   # List Index
- SRC_LIST = values{}   # " " Source List Values
- currentIndex = @Value(currentIndex)

INPUT (input)
    -> ListCopier_3
ListCopier_3
    SRC_LIST = $(LIST_ATTR)
    DEST_LIST = _fields
    -> ListCopier_2
ListCopier_2
    SRC_LIST = $(SRC_LIST)
    DEST_LIST = _values
    -> AttributeExposer_3
AttributeExposer_3
    ATTR_LIST = _fields{},_fields,_element_count,_values{},_values
    -> ListIndexer_27
ListIndexer_27
    INDEX = $(INDEX)
    LIST_ATTR = _fields{}
    -> ListIndexer_2
ListIndexer_2
    INDEX = $(INDEX)
    LIST_ATTR = _values{}
    -> TCL_AttributeAdd
TCL_AttributeAdd: TCLCaller
    SRC = proc attrAdd {attr value} {  FME_SetAttribute $attr $value   }
    VAL_ATTR = _result
    TCLPROG = attrAdd &_fields &_values
    -> ExpressionEvaluator
ExpressionEvaluator
    EXPRESSION = $(currentIndex)+1
    VAL_ATTR = currentIndex
    -> Tester_5
Tester_5
    TEST_CLAUSE = TEST @Value(currentIndex) < @Value(_element_count)
    TEST_MODE = Automatic
    BOOL_OP = OR
    TEST_LIST = &currentIndex,<,&_element_count
    FAILED -> OUTPUT (output)
    PASSED -> INPUT (output)
INPUT (output)
OUTPUT (output)
