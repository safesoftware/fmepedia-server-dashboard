FME workspace JobsPerEngine_RESTVersion.fmw
Title: none2none

Parameters:
- Max_job_age = 1 day ago   # Only include jobs from

Writers:
- CSV_1: CSV to $(FME_SHAREDRESOURCE_DATA)ServerDashboard

Creator
    GEOMTYPE = Geometry Object
    NUM = 1
    CREATED -> JobHistoryReader
JobHistoryReader
    SERVER_HOST = https://demos-safe-software.fmecloud.com
    SERVER_TOKEN =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
    MAX_JOB_AGE = $(Max_job_age)
    Server_Version = v2
    -> StringReplacer
    <Rejected> -> JobHistoryReader__Rejected_
DateFormatter
    DATE_ATTR = timeFinished
    FMT = FME Date (%Y%m%d)
    SRCFMT = Unknown - Automatic Detection
    INVALID_DATE_VALUE = _FME_NO_OP_
    -> Aggregator_2
Note: Sort by Date for chart
Sorter
    SORT_PARM = SortDate NUMERIC ASCENDING
    SORTED -> jobsPerEngine (writer CSV_1)
jobsPerEngine (writer CSV_1)
    attributes: Date auto, localhost_Engine1 auto, localhost_Engine2 auto, localhost_Engine3 auto, localhost_Engine4 auto, localhost_Engine5 auto, localhost_Engine6 auto, localhost_Engine7 auto, localhost_Engine8 auto, localhost_Engine9 auto, localhost_Engine10 auto, localhost_Engine11 auto, localhost_Engine12 auto, localhost_Engine13 auto, localhost_Engine14 auto, localhost_Engine15 auto, TotalJobsRun auto
JobHistoryReader__Rejected_: Logger
    MESSAGE = Feature is:
    MAXFEATS = 20
    MAXCOORDS = 20

Bookmark: Get workspace and repository name
StringReplacer
    NO_MATCH = _FME_NO_OP_
    CASE = no
    SRC_ATTRS = workspacePath
    FIND_TEXT = "
    REGEXP = no
    -> FilenamePartExtractor
FilenamePartExtractor
    SRC_ATTR = @Value(workspacePath)
    DIRPATH_ATTR = folderpath
    FULLNAME_ATTR = WorkspaceName
    -> AttributeSplitter_2
AttributeSplitter_2
    DELIMITER = /
    TRIM_OPTION = Both
    LIST_NAME = _path
    DROP_EMPTY_PARTS = No
    ATTR_NAME = folderpath
    -> AttributeCreator_3
AttributeCreator_3
    ATTR_LIST = Repository,@Value(_path{0})
    -> DateFormatter

Bookmark: Num Jobs per Engine
Aggregator_2
    ACCUM_ATTRS_NAME = Yes
    SEP = ,
    MODE = Attributes Only
    ORDERED = No
    COUNT_ATTR = JobsRun
    GROUP_BY = engineName timeFinished
    AGGREGATE -> AttributeKeeper_2

Bookmark: Attribute cleanup
AttributeKeeper_2
    KEEP_ATTRS = JobsRun,engineName,timeFinished
    -> AttributeCreator_5
AttributeCreator_5
    ATTR_LIST = Date,@Value(timeFinished)
    -> Aggregator

Bookmark: Group by Date
Aggregator
    LIST_NAME = _list
    ACCUM_ATTRS_NAME = Yes
    SEP = ,
    MODE = Attributes Only
    ORDERED = No
    GROUP_BY = Date
    AGGREGATE -> ListRenamer
ListRenamer
    LIST_COMPONENT_NAMES = _list{},_list{},engineName{},engineName{}
    LIST_ACTION = Promote
    LEAVE_ORIG = No
    LIST_NAME = _list{}.engineName
    -> ListRenamer_2
ListRenamer_2
    LIST_COMPONENT_NAMES = _list{},_list{},JobsRun{},JobsRun{}
    LIST_ACTION = Promote
    LEAVE_ORIG = No
    LIST_NAME = _list{}.JobsRun
    -> RecordBuilder
RecordBuilder
    SRC_LIST = JobsRun{}
    LIST_ATTR = engineName{}
    -> AttributeCreator

Bookmark: Format date
AttributeCreator
    ATTR_LIST = SortDate,@Value(Date)
    -> DateFormatter_6
DateFormatter_6
    DATE_ATTR = Date
    FMT = %D
    SRCFMT = Unknown - Automatic Detection
    INVALID_DATE_VALUE = _FME_NO_OP_
    -> AttributeExposer_2

Bookmark: Prep Attributes for output
AttributeExposer_2
    ATTR_LIST = localhost_Engine1,localhost_Engine2,localhost_Engine3,localhost_Engine4,localhost_Engine5,localhost_Engine6,localhost_Engine7,localhost_Engine8,localhost_Engine9,localhost_Engine10,localhost_Engine11,localhost_Engine12,localhost_Engine13,localhost_Engine14,localhost_Engine15
    -> NullAttributeMapper
NullAttributeMapper
    ATTRLIST = localhost_Engine1 localhost_Engine2 localhost_Engine3 localhost_Engine4
    NEW_VALUE = 0
    ATTRCHOICE = Selected Attributes
    NULL_TREATMENT = New Value
    SOURCE_ATTR_VAL = "Missing (Selected Attributes Only)"
    -> ListSummer
ListSummer
    SRC_LIST = JobsRun{}
    RESULT = TotalJobsRun
    -> Sorter

FME custom transformer RecordBuilder
Creates new attributes from field name and value pairs. Input is a field{} list and a value{} list. Output are new fields as follows:
=
=
etc
Depends on RecordBuilderLoop to iterate through the field{} and value{} lists.

Parameters:
- LIST_ATTR = _fields{}   # " " Field Names List
- SRC_LIST = _values{}   # " " Field Values List
- REMOVE_ATTRS = _creation_instance,_element_count,_fields,_result,_values,currentIndex,field0,field1,field2,value0,value1,value2   # " " Attributes to Remove

INPUT (input)
    -> ListCopier_3
ListCopier_3
    SRC_LIST = $(LIST_ATTR)
    DEST_LIST = _fields
    -> ListCopier_2
ListCopier_2
    SRC_LIST = $(SRC_LIST)
    DEST_LIST = _values
    -> AttributeExposer_3
Note: RecordBuilder / Creates new attributes from field name and value pairs. / Input is a field{} list and a value{} list. / Output are new fields as follows: / <field1>=<value1> / <field2>=<value2> / etc / Depends on RecordBuilderLoop to iterate through the field{} and value{} lists.
AttributeExposer_3
    ATTR_LIST = _fields{},_fields,_values{},_values
    -> ListElementCounter
ListElementCounter
    CNT_ATTR = _element_count
    LIST_NAME = _fields{}
    -> AttributeCreator_3
AttributeCreator_3
    ATTR_LIST = currentIndex,0
    -> RecordBuilderLoop
RecordBuilderLoop
    SRC_LIST = _values{}
    INDEX = @Value(currentIndex)
    LIST_ATTR = _fields{}
    currentIndex = @Value(currentIndex)
    -> AttributeRemover
AttributeRemover
    REMOVE_ATTRS = $(REMOVE_ATTRS)
    -> ListRemover
ListRemover
    LIST_ATTRS = _fields{} _values{}
    -> OUTPUT (output)
OUTPUT (output)

FME custom transformer JobHistoryReader

Parameters:
- SERVER_HOST =   # FME Server URL
- SERVER_TOKEN =   # FME Server Token
- MAX_JOB_AGE = 1 month ago   # " " Maximum Job Age
- Server_Version = v3   # FME Server 2015 or older,v2%FME Server 2016 or newer,v3 Server Version

Input (input)
    -> AttributeCreator
AttributeCreator
    ATTR_LIST = _offset,0,_max_job_age,$(MAX_JOB_AGE)
    -> HTTPCaller
LoopHere (input)
    -> AttributeExposer
AttributeExposer
    ATTR_LIST = _offset
    -> AttributeCreator_2
AttributeCreator_2
    ATTR_LIST = _offset,@Evaluate(@Value(_offset)+1000)
    -> HTTPCaller
HTTPCaller
    HTTP_METHOD = GET
    TARGET_ATTR_ENCODING = auto-detect
    RESPONSE_HEADER_LIST_ATTR = _headers
    USE_COOKIES = No
    FOLLOW_REDIRECTS = Yes
    TARGET_URL = $(SERVER_HOST)/fmerest/$(Server_Version)/transformations/jobs/completed
    SAVE_FILE = Attribute
    TARGET_ATTR = _response_body
    CONNECTION_TIMEOUT_LENGTH = 60
    VERIFY_SSL_CERTIFICATES = Yes
    CUSTOM_HEADERS = Authorization;fmetoken token=$(SERVER_TOKEN)
    ADDITIONAL_URL_PARAMETERS = limit;1000 offset;@Value(_offset) detail;high
    TRANSFER_TIMEOUT_LENGTH = 90
    ERROR_ATTR = _error
    STATUS_CODE_ATTR = _http_status_code
    <Rejected> -> <Rejected> (output)
    -> JSONFragmenter
JSONFragmenter
    JSON_QUERY = json[*]
    JSON_ATTR = _response_body
    EXTRACT_ATTR = Yes
    RECURSIVE = Yes
    EXPLODE_FORMAT = JSON
    NEW_ATTRIBUTES = timeFinished timeStarted status result.statusMessage result.id request.workspacePath engineName
    EXPLODED -> DateFormatter
DateFormatter
    DATE_ATTR = _max_job_age
    FMT = FME Date/Time (%Y%m%d%H%M%S)
    SRCFMT = Unknown - Automatic Detection
    INVALID_DATE_VALUE = _FME_NO_OP_
    -> DateFormatter_2
DateFormatter_2
    DATE_ATTR = timeFinished
    FMT = FME Date/Time (%Y%m%d%H%M%S)
    SRCFMT = Unknown - Automatic Detection
    INVALID_DATE_VALUE = _FME_NO_OP_
    -> Tester
Tester
    BOOL_OP = OR
    TEST_MODE = Automatic
    TEST_CLAUSE = TEST @Value(timeFinished) >= @Value(_max_job_age)
    TEST_DESCRIPTION = ""
    PASSED -> Sampler
    PASSED -> BulkAttributeRenamer
BulkAttributeRenamer
    PATTERN_ACTION_DISP = Remove Prefix String
    CASE_DISP = yes
    ATTRCHOICE = All Attributes
    REPLACE_STR = result.
    -> BulkAttributeRenamer_2
BulkAttributeRenamer_2
    PATTERN_ACTION_DISP = Remove Prefix String
    CASE_DISP = yes
    ATTRCHOICE = All Attributes
    REPLACE_STR = request.
    -> Output (output)
Output (output)
Sampler
    RATE = 1000
    SAMPLE_TYPE_LONG = Every Nth Feature
    SAMPLED -> AttributeKeeper
AttributeKeeper
    KEEP_ATTRS = _offset,_max_job_age
    -> LoopHere (output)
LoopHere (output)
<Rejected> (output)

FME custom transformer RecordBuilderLoop
Indexes lists from RecordBuilder and creates new attributes from field name and value pairs. Input is a field{} list and a value{} list. Output are new fields as follows:
=
=
etc

Parameters:
- LIST_ATTR = _fields{}   # " " List Fields
- INDEX = @Value(currentIndex)   # List Index
- SRC_LIST = values{}   # " " Source List Values
- currentIndex = @Value(currentIndex)

INPUT (input)
    -> ListCopier_3
ListCopier_3
    SRC_LIST = $(LIST_ATTR)
    DEST_LIST = _fields
    -> ListCopier_2
ListCopier_2
    SRC_LIST = $(SRC_LIST)
    DEST_LIST = _values
    -> AttributeExposer_3
AttributeExposer_3
    ATTR_LIST = _fields{},_fields,_element_count,_values{},_values
    -> ListIndexer_27
ListIndexer_27
    INDEX = $(INDEX)
    LIST_ATTR = _fields{}
    -> ListIndexer_2
ListIndexer_2
    INDEX = $(INDEX)
    LIST_ATTR = _values{}
    -> TCL_AttributeAdd
TCL_AttributeAdd: TCLCaller
    SRC = proc attrAdd {attr value} {  FME_SetAttribute $attr $value   }
    TCLPROG = attrAdd &_fields &_values
    VAL_ATTR = _result
    -> ExpressionEvaluator
ExpressionEvaluator
    VAL_ATTR = currentIndex
    EXPRESSION = $(currentIndex)+1
    -> Tester_5
Tester_5
    BOOL_OP = OR
    TEST_MODE = Automatic
    TEST_CLAUSE = TEST @Value(currentIndex) < @Value(_element_count)
    TEST_LIST = &currentIndex,<,&_element_count
    FAILED -> OUTPUT (output)
    PASSED -> INPUT (output)
INPUT (output)
OUTPUT (output)
