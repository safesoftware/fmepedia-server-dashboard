FME workspace RuntimePerEngine_RESTVersion.fmw
Title: none2none

Parameters:
- Max_Job_Age = 1 hour ago   # Get jobs from
- SERVER_HOST =   # FME Server URL
- SERVER_TOKEN =   # FME Server Token

Writers:
- CSV_1: CSV to $(FME_SHAREDRESOURCE_DATA)ServerDashboard

Creator
    NUM = 1
    GEOMTYPE = Geometry Object
    CREATED -> JobHistoryReader_2
JobHistoryReader_2
    SERVER_HOST = $(SERVER_HOST)
    MAX_JOB_AGE = $(Max_Job_Age)
    SERVER_TOKEN = $(SERVER_TOKEN)
    Server_Version = v2
    -> AttributeCopier
    <Rejected> -> JobHistoryReader__Rejected_
Note: Calculate total runtime / per engine
Aggregator
    ORDERED = No
    MODE = Attributes Only
    SEP = ,
    ACCUM_ATTRS_NAME = Yes
    GROUP_BY = Date engineName
    SUM = RunTime
    AGGREGATE -> AttributeCreator_3
AttributeCreator_3
    ATTR_LIST = SortDate,@Value(Date)
    -> DateFormatter_6
DateFormatter_6
    SRCFMT = Unknown - Automatic Detection
    INVALID_DATE_VALUE = _FME_NO_OP_
    DATE_ATTR = Date
    FMT = %b %e
    -> Aggregator_2
Note: Sort by date
Sorter
    SORT_PARM = _list{0}.SortDate ALPHA ASCENDING
    SORTED -> runtimePerEngine (writer CSV_1)
runtimePerEngine (writer CSV_1)
    attributes: Date auto, localhost_Engine1 auto, localhost_Engine2 auto, localhost_Engine3 auto, localhost_Engine4 auto, localhost_Engine5 auto, localhost_Engine6 auto, localhost_Engine7 auto, localhost_Engine8 auto, localhost_Engine9 auto, localhost_Engine10 auto, localhost_Engine11 auto, localhost_Engine12 auto, localhost_Engine13 auto, localhost_Engine14 auto, localhost_Engine15 auto, TotalRunTime auto
JobHistoryReader__Rejected_: Logger
    MESSAGE = Feature is:
    MAXFEATS = 20
    MAXCOORDS = 20

Bookmark: Calculate Run Time
AttributeCopier
    ATTR_LIST = timeFinished,date_finished_epoch,,timeStarted,date_started_epoch,
    -> DateFormatter_3
DateFormatter_3
    SRCFMT = Unknown - Automatic Detection
    INVALID_DATE_VALUE = _FME_NO_OP_
    DATE_ATTR = date_finished_epoch,date_started_epoch
    FMT = %s
    -> AttributeCreator_2
AttributeCreator_2
    ATTR_LIST = RunTime,@Evaluate(@Value(date_finished_epoch)-@Value(date_started_epoch))
    -> DateFormatter

Bookmark: Attribute Cleanup
DateFormatter
    SRCFMT = Unknown - Automatic Detection
    INVALID_DATE_VALUE = _FME_NO_OP_
    DATE_ATTR = timeFinished
    FMT = FME Date (%Y%m%d)
    -> AttributeKeeper_2
AttributeKeeper_2
    KEEP_ATTRS = RunTime,engineName,timeFinished
    -> AttributeCreator_5
AttributeCreator_5
    ATTR_LIST = Date,@Value(timeFinished)
    -> Aggregator

Bookmark: Group by Date
Aggregator_2
    ORDERED = No
    LIST_NAME = _list
    MODE = Attributes Only
    SEP = ,
    ACCUM_ATTRS_NAME = Yes
    GROUP_BY = Date
    AGGREGATE -> ListRenamer
ListRenamer
    LIST_NAME = _list{}.engineName
    LIST_COMPONENT_NAMES = _list{},_list{},engineName{},engineName{}
    LIST_ACTION = Promote
    LEAVE_ORIG = No
    -> ListRenamer_2
ListRenamer_2
    LIST_NAME = _list{}.RunTime
    LIST_COMPONENT_NAMES = _list{},_list{},RunTime{},RunTime{}
    LIST_ACTION = Promote
    LEAVE_ORIG = No
    -> RecordBuilder
RecordBuilder
    LIST_ATTR = engineName{}
    SRC_LIST = RunTime{}
    -> AttributeExposer_3

Bookmark: Create attributes for output
AttributeExposer_3
    ATTR_LIST = localhost_Engine1,localhost_Engine2,localhost_Engine3,localhost_Engine4,localhost_Engine5,localhost_Engine6,localhost_Engine7,localhost_Engine8,localhost_Engine9,localhost_Engine10,localhost_Engine11,localhost_Engine12,localhost_Engine13,localhost_Engine14,localhost_Engine15
    -> NullAttributeMapper
NullAttributeMapper
    ATTRCHOICE = Selected Attributes
    NEW_VALUE = 0
    SOURCE_ATTR_VAL = "Missing (Selected Attributes Only)"
    NULL_TREATMENT = New Value
    ATTRLIST = localhost_Engine1 localhost_Engine2 localhost_Engine3 localhost_Engine4
    -> ListSummer
ListSummer
    RESULT = TotalRunTime
    SRC_LIST = RunTime{}
    -> Sorter

FME custom transformer RecordBuilderLoop
Indexes lists from RecordBuilder and creates new attributes from field name and value pairs. Input is a field{} list and a value{} list. Output are new fields as follows:
=
=
etc

Parameters:
- LIST_ATTR = _fields{}   # " " List Fields
- INDEX = @Value(currentIndex)   # List Index
- SRC_LIST = values{}   # " " Source List Values
- currentIndex = @Value(currentIndex)

INPUT (input)
    -> ListCopier_3
ListCopier_3
    DEST_LIST = _fields
    SRC_LIST = $(LIST_ATTR)
    -> ListCopier_2
ListCopier_2
    DEST_LIST = _values
    SRC_LIST = $(SRC_LIST)
    -> AttributeExposer_3
AttributeExposer_3
    ATTR_LIST = _fields{},_fields,_element_count,_values{},_values
    -> ListIndexer_27
ListIndexer_27
    LIST_ATTR = _fields{}
    INDEX = $(INDEX)
    -> ListIndexer_2
ListIndexer_2
    LIST_ATTR = _values{}
    INDEX = $(INDEX)
    -> TCL_AttributeAdd
TCL_AttributeAdd: TCLCaller
    VAL_ATTR = _result
    TCLPROG = attrAdd &_fields &_values
    SRC = proc attrAdd {attr value} {  FME_SetAttribute $attr $value   }
    -> ExpressionEvaluator
ExpressionEvaluator
    VAL_ATTR = currentIndex
    EXPRESSION = $(currentIndex)+1
    -> Tester_5
Tester_5
    TEST_CLAUSE = TEST @Value(currentIndex) < @Value(_element_count)
    TEST_LIST = &currentIndex,<,&_element_count
    BOOL_OP = OR
    TEST_MODE = Automatic
    FAILED -> OUTPUT (output)
    PASSED -> INPUT (output)
INPUT (output)
OUTPUT (output)

FME custom transformer RecordBuilder
Creates new attributes from field name and value pairs. Input is a field{} list and a value{} list. Output are new fields as follows:
=
=
etc
Depends on RecordBuilderLoop to iterate through the field{} and value{} lists.

Parameters:
- LIST_ATTR = _fields{}   # " " Field Names List
- SRC_LIST = _values{}   # " " Field Values List
- REMOVE_ATTRS = _creation_instance,_element_count,_fields,_result,_values,currentIndex,field0,field1,field2,value0,value1,value2   # " " Attributes to Remove

INPUT (input)
    -> ListCopier_3
ListCopier_3
    DEST_LIST = _fields
    SRC_LIST = $(LIST_ATTR)
    -> ListCopier_2
ListCopier_2
    DEST_LIST = _values
    SRC_LIST = $(SRC_LIST)
    -> AttributeExposer_3
Note: RecordBuilder / Creates new attributes from field name and value pairs. / Input is a field{} list and a value{} list. / Output are new fields as follows: / <field1>=<value1> / <field2>=<value2> / etc / Depends on RecordBuilderLoop to iterate through the field{} and value{} lists.
AttributeExposer_3
    ATTR_LIST = _fields{},_fields,_values{},_values
    -> ListElementCounter
ListElementCounter
    LIST_NAME = _fields{}
    CNT_ATTR = _element_count
    -> AttributeCreator_3
AttributeCreator_3
    ATTR_LIST = currentIndex,0
    -> RecordBuilderLoop
RecordBuilderLoop
    LIST_ATTR = _fields{}
    INDEX = @Value(currentIndex)
    SRC_LIST = _values{}
    currentIndex = @Value(currentIndex)
    -> AttributeRemover
AttributeRemover
    REMOVE_ATTRS = $(REMOVE_ATTRS)
    -> ListRemover
ListRemover
    LIST_ATTRS = _fields{} _values{}
    -> OUTPUT (output)
OUTPUT (output)
