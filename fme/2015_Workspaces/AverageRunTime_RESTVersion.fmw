FME workspace AverageRunTime_RESTVersion.fmw
Title: none2none

Parameters:
- Max_job_age = 1 hour ago   # Only include jobs from

Writers:
- CSV_1: CSV to $(FME_SHAREDRESOURCE_DATA)ServerDashboard

Creator
    GEOMTYPE = Geometry Object
    NUM = 1
    CREATED -> JobHistoryReader
JobHistoryReader
    SERVER_HOST = https://demos-safe-software.fmecloud.com
    SERVER_TOKEN =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
    MAX_JOB_AGE = $(Max_job_age)
    Server_Version = v2
    <Rejected> -> JobHistoryReader__Rejected_
    -> AttributeCopier
AttributeKeeper
    KEEP_ATTRS = Repository,RunTime,WorkspaceName
    -> StatisticsCalculator
StatisticsCalculator
    STATS_ATTRS = RunTime
    COMPUTE_HISTOGRAM = NO
    MEDIAN_ATTR = AverageRunTime
    PREPEND_ATTR_NAME_CHOICE = For multiple results only
    GROUP_BY = Repository WorkspaceName
    SUMMARY -> AttributeCreator_2
AttributeCreator_2
    ATTR_LIST = WorkspaceName,<b>@Value(Repository)</b><br/>@Value(WorkspaceName),forSorting,@LowerCase(@Value(WorkspaceName))
    -> Tester
Tester
    BOOL_OP = OR
    TEST_MODE = Automatic
    TEST_CLAUSE = TEST @Value(AverageRunTime) NOT_= 0
    TEST_DESCRIPTION = ""
    PASSED -> Sorter
Sorter
    SORT_PARM = forSorting ALPHA ASCENDING
    SORTED -> averageRunTime (writer CSV_1)
averageRunTime (writer CSV_1)
    attributes: WorkspaceName char(100), AverageRunTime auto
JobHistoryReader__Rejected_: Logger
    MESSAGE = Feature is:
    MAXFEATS = 20
    MAXCOORDS = 20

Bookmark: Calculate Run Time
AttributeCopier
    ATTR_LIST = timeFinished,date_finished_epoch,,timeStarted,date_started_epoch,
    -> DateFormatter
DateFormatter
    DATE_ATTR = date_finished_epoch,date_started_epoch
    FMT = %s
    SRCFMT = Unknown - Automatic Detection
    INVALID_DATE_VALUE = _FME_NO_OP_
    -> AttributeCreator
AttributeCreator
    ATTR_LIST = RunTime,@Evaluate(@Value(date_finished_epoch)-@Value(date_started_epoch))
    -> StringReplacer

Bookmark: Get workspace and repository name
StringReplacer
    NO_MATCH = _FME_NO_OP_
    CASE = no
    SRC_ATTRS = workspacePath
    FIND_TEXT = "
    REGEXP = no
    -> FilenamePartExtractor
FilenamePartExtractor
    SRC_ATTR = @Value(workspacePath)
    DIRPATH_ATTR = folderpath
    FULLNAME_ATTR = WorkspaceName
    -> AttributeSplitter_2
AttributeSplitter_2
    DELIMITER = /
    TRIM_OPTION = Both
    LIST_NAME = _path
    DROP_EMPTY_PARTS = No
    ATTR_NAME = folderpath
    -> AttributeCreator_3
AttributeCreator_3
    ATTR_LIST = Repository,@Value(_path{0})
    -> AttributeKeeper

FME custom transformer JobHistoryReader

Parameters:
- SERVER_HOST =   # FME Server URL
- SERVER_TOKEN =   # FME Server Token
- MAX_JOB_AGE = 1 month ago   # " " Maximum Job Age
- Server_Version = v3   # FME Server 2015 or older,v2%FME Server 2016 or newer,v3 Server Version

Input (input)
    -> AttributeCreator
AttributeCreator
    ATTR_LIST = _offset,0,_max_job_age,$(MAX_JOB_AGE)
    -> HTTPCaller
LoopHere (input)
    -> AttributeExposer
AttributeExposer
    ATTR_LIST = _offset
    -> AttributeCreator_2
AttributeCreator_2
    ATTR_LIST = _offset,@Evaluate(@Value(_offset)+1000)
    -> HTTPCaller
HTTPCaller
    HTTP_METHOD = GET
    TARGET_ATTR_ENCODING = auto-detect
    RESPONSE_HEADER_LIST_ATTR = _headers
    USE_COOKIES = No
    FOLLOW_REDIRECTS = Yes
    TARGET_URL = $(SERVER_HOST)/fmerest/$(Server_Version)/transformations/jobs/completed
    SAVE_FILE = Attribute
    TARGET_ATTR = _response_body
    CONNECTION_TIMEOUT_LENGTH = 60
    VERIFY_SSL_CERTIFICATES = Yes
    CUSTOM_HEADERS = Authorization;fmetoken token=$(SERVER_TOKEN)
    ADDITIONAL_URL_PARAMETERS = limit;1000 offset;@Value(_offset) detail;high
    TRANSFER_TIMEOUT_LENGTH = 90
    ERROR_ATTR = _error
    STATUS_CODE_ATTR = _http_status_code
    <Rejected> -> <Rejected> (output)
    -> JSONFragmenter
JSONFragmenter
    JSON_QUERY = json[*]
    JSON_ATTR = _response_body
    EXTRACT_ATTR = Yes
    RECURSIVE = Yes
    EXPLODE_FORMAT = JSON
    NEW_ATTRIBUTES = timeFinished timeStarted status result.statusMessage result.id request.workspacePath engineName
    EXPLODED -> DateFormatter
DateFormatter
    DATE_ATTR = _max_job_age
    FMT = FME Date/Time (%Y%m%d%H%M%S)
    SRCFMT = Unknown - Automatic Detection
    INVALID_DATE_VALUE = _FME_NO_OP_
    -> DateFormatter_2
DateFormatter_2
    DATE_ATTR = timeFinished
    FMT = FME Date/Time (%Y%m%d%H%M%S)
    SRCFMT = Unknown - Automatic Detection
    INVALID_DATE_VALUE = _FME_NO_OP_
    -> Tester
Tester
    BOOL_OP = OR
    TEST_MODE = Automatic
    TEST_CLAUSE = TEST @Value(timeFinished) >= @Value(_max_job_age)
    TEST_DESCRIPTION = ""
    PASSED -> Sampler
    PASSED -> BulkAttributeRenamer
BulkAttributeRenamer
    PATTERN_ACTION_DISP = Remove Prefix String
    CASE_DISP = yes
    ATTRCHOICE = All Attributes
    REPLACE_STR = result.
    -> BulkAttributeRenamer_2
BulkAttributeRenamer_2
    PATTERN_ACTION_DISP = Remove Prefix String
    CASE_DISP = yes
    ATTRCHOICE = All Attributes
    REPLACE_STR = request.
    -> Output (output)
Output (output)
Sampler
    RATE = 1000
    SAMPLE_TYPE_LONG = Every Nth Feature
    SAMPLED -> AttributeKeeper
AttributeKeeper
    KEEP_ATTRS = _offset,_max_job_age
    -> LoopHere (output)
LoopHere (output)
<Rejected> (output)
